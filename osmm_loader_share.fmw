FME workspace osmm_loader_share.fmw

Parameters:
- SourceDataset_DNF_3 = path/to/folder/*.gz   # Source OS (GB) MasterMap File(s)
- Schema = osmm_nov_2015_fme
- DestDataset_POSTGIS_1 = Enter Database   # Database
- POSTGIS_OUT_HOST_POSTGIS = Enter Host   # Host
- POSTGIS_OUT_USER_NAME_POSTGIS = Enter username   # Username
- POSTGIS_OUT_PASSWORD_POSTGIS =   # Password

Readers:
- DNF_1: DNF from $(SourceDataset_DNF_3)

Writers:
- POSTGIS_1: POSTGIS to $(DestDataset_POSTGIS_1)

Note: Ordnance Survey MasterMap Topographic Layer Loader / This workspace is designed to load .gz files into PostGIS. Run with prompt to change the folder location and the database connection details. / Important: FME will not create the schema in PostGIS. You will need to create the schema first and use that name in the schema parameter. / When loading multiple .gz files it is likley contain duplicate feartures. These will need to be removed after loading.
Note: All the .gz file you wish to load need to be in the same folder. In the prompt window, you need to select the Advanced Bowser option and add the folder.

Bookmark: Inputs
TopographicLine (reader DNF_1)
    attributes: TOID xml_char(16), FeatureCode xml_int16, Version xml_int16, VersionDate xml_char(10), Theme xml_char(64), ThemeCount xml_int16, AccuracyOfPosition xml_char(7), ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, NonBoundingLine xml_boolean, HeightAboveDatum xml_real64, AccuracyOfHeightAboveDatum xml_char(7), HeightAboveGroundLevel xml_real64, AccuracyOfHeightAboveGroundLevel xml_char(7), Make xml_char(12), PhysicalLevel xml_int16, PhysicalPresence xml_char(16), ReferenceToFeature xml_char(16), broken xml_char(5)
    -> BulkAttributeRenamer_3
BoundaryLine (reader DNF_1)
    attributes: TOID xml_char(16), FeatureCode xml_int16, Version xml_int16, VersionDate xml_char(10), Theme xml_char(64), ThemeCount xml_int16, AccuracyOfPosition xml_char(7), ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, Make xml_char(12), PhysicalLevel xml_int16, PhysicalPresence xml_char(16), broken xml_char(5)
    -> BulkAttributeRenamer_3
CartographicSymbol (reader DNF_1)
    attributes: xml_rotation xml_real64, TOID xml_char(16), FeatureCode xml_int16, Version xml_int16, VersionDate xml_char(10), Theme xml_char(64), ThemeCount xml_int16, ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, Orientation xml_int16, PhysicalLevel xml_int16, PhysicalPresence xml_char(16), ReferenceToFeature{} xml_char(16)
    -> BulkAttributeRenamer_3
CartographicText (reader DNF_1)
    attributes: TOID xml_char(16), FeatureCode xml_int16, Version xml_int16, VersionDate xml_char(10), Theme xml_char(64), ThemeCount xml_int16, ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, Make xml_char(12), PhysicalLevel xml_int16, PhysicalPresence xml_char(16), AnchorPosition xml_decimal(3,0), Font xml_decimal(3,0), Height xml_real32, Orientation xml_int16, TextString xml_char(254)
    -> BulkAttributeRenamer_3
TopographicArea (reader DNF_1)
    attributes: TOID xml_char(16), FeatureCode xml_int16, Version xml_int16, VersionDate xml_char(10), Theme xml_char(64), ThemeCount xml_int16, CalculatedAreaValue xml_real64, ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, Make xml_char(12), PhysicalLevel xml_int16, PhysicalPresence xml_char(16), broken xml_char(5)
    -> BulkAttributeRenamer_3
TopographicPoint (reader DNF_1)
    attributes: TOID xml_char(16), FeatureCode xml_int16, Version xml_int16, VersionDate xml_char(10), Theme xml_char(64), ThemeCount xml_int16, AccuracyOfPosition xml_char(7), ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, HeightAboveDatum xml_real64, AccuracyOfHeightAboveDatum xml_char(7), HeightAboveGroundLevel xml_real64, AccuracyOfHeightAboveGroundLevel xml_char(7), Make xml_char(12), PhysicalLevel xml_int16, PhysicalPresence xml_char(16), ReferenceToFeature xml_char(16)
    -> BulkAttributeRenamer_3
queryExtent (reader DNF_1)
    -> TimeStamper

Bookmark: Attribute prep
Note: Makes all the attributes Lowercase
BulkAttributeRenamer_3
    CASE_CHANGE_TYPE = lowercase
    ATTRCHOICE = All Attributes
    PATTERN_ACTION_DISP = Change Case
    -> ListConcatenator

Bookmark: Process and Flatten Change History
Note: Concatonates change date values
ListConcatenator
    SEP = ,
    DROP_EMPTY_PARTS = No
    VAL_ATTR = changedate
    LIST_ATTR = changehistory{}.changedate
    -> ListConcatenator_2
Note: Concatontates change reason values
ListConcatenator_2
    SEP = ,
    DROP_EMPTY_PARTS = No
    VAL_ATTR = reasonforchange
    LIST_ATTR = changehistory{}.reasonforchange
    -> ListRangeExtractor
Note: Extacts start and end date range
ListRangeExtractor
    MIN = firstchangedate
    SRC_LIST = changehistory{}.changedate
    MAX = lastchangedate
    -> AttributeExposer_2

Bookmark: Identify tile name
Note: Expose fme_basename
AttributeExposer_2
    ATTR_LIST = fme_basename
    -> AttributeSplitter_2
Note: Splits the basename
AttributeSplitter_2
    TRIM_OPTION = Both
    DELIMITER = -
    DROP_EMPTY_PARTS = No
    ATTR_NAME = fme_basename
    LIST_NAME = _lstTileName
    -> AttributeCreator_2
Note: Extract tile name from list
AttributeCreator_2
    ATTR_LIST = tilename,@Value(_lstTileName{1})
    -> AttributeRemover_2

Bookmark: Attribute tidy-up
Note: Removes redundant attributes and lists
AttributeRemover_2
    LIST_ATTRS = _lstTileName{} changehistory{} changehistory{}.changedate changehistory{}.reasonforchange
    REMOVE_ATTRS = accuracyofheightabovedatum,accuracyofheightabovegroundlevel,accuracyofposition,changehistorycount,descriptivegroupcount,descriptivetermcount,firstchangedate,fme_basename,heightabovedatum,heightabovegroundlevel,themecount,xml_rotation,broken,calculatedareavalue,nonboundingline
    -> UUIDGenerator

Bookmark: Set Attributes
Note: Generates a Universal Unique ID
UUIDGenerator
    UUID_ATTR = uuid
    -> TimeStamper_2
Note: Create a Load Date Attribute
TimeStamper_2
    FMT = FME Date/Time (^Y^m^d^H^M^S)
    TIME_ATTR = loaddate
    -> ListConcatenator_3
Note: Concats the reference to feature values
ListConcatenator_3
    SEP = ,
    DROP_EMPTY_PARTS = Yes
    VAL_ATTR = referencetofeature
    LIST_ATTR = referencetofeature{}
    -> StringConcatenator
Note: Concats "osgbn" onto the TOID number
StringConcatenator
    PARM_LINE = osgb@Value(toid)
    VAL_ATTR = toid
    -> AttributeRemover

Bookmark: Attribute tidy-up 2
Note: Removes further redudant attributes and lists
AttributeRemover
    LIST_ATTRS = referencetofeature{}
    -> NullAttributeMapper
Note: Converts Missing and Empty Values to NULL
NullAttributeMapper
    SOURCE_ATTR_VAL = Null Empty "Missing (Selected Attributes Only)"
    NULL_TREATMENT = Null
    ATTRCHOICE = Selected Attributes
    ATTRLIST = anchorposition changedate descriptivegroup descriptiveterm featurecode font height lastchangedate loaddate make orientation physicallevel physicalpresence reasonforchange referencetofeature textstring theme tilename toid uuid version versiondate
    -> FeatureTypeFilter

Bookmark: Filter Data into Feature Types
Note: Filters the data back out on the feature type
FeatureTypeFilter
    ATTRIBUTES = <BLANK>,<UNFILTERED>,CartographicText,TopographicLine,TopographicArea,CartographicSymbol,BoundaryLine,TopographicPoint
    CartographicText -> CT_Style_Creator
    TopographicLine -> TL_Style_Creator
    TopographicArea -> TA_Style_Creator
    CartographicSymbol -> CS_Style_Creator
    BoundaryLine -> BL_Style_Creator
    TopographicPoint -> TP_Style_Creator

Bookmark: Set Style ID
Note: This is where the magic happens. These attribute creators contain multiple conditional values which mimic the SQL statements from OS resulting on columns and values that the stylesheets rely on
CT_Style_Creator: AttributeCreator
    ATTR_LIST = style_description,"FME_CONDITIONAL:DEFAULT_VALUE'Unclassified'BOOL_OP;OR;COMPOSITE_TEST;<Unused>;TEST @Value(descriptivegroup) CONTAINS Buildings Or Structure'Building Text'BOOL_OP;OR;COMPOSITE_TEST;<Unused>;TEST @Value(descriptivegroup) CONTAINS Inland Water'Water Text'BOOL_OP;OR;COMPOSITE_TEST;<Unused>;TEST @Value(descriptivegroup) CONTAINS Road Or Track'Road Text'BOOL_OP;OR;COMPOSITE_TEST;<Unused>;TEST @Value(descriptivegroup) = Terrain And Height'Height Text'BOOL_OP;OR;COMPOSITE_TEST;<Unused>;TEST @Value(descriptivegroup) CONTAINS Roadside'Roadside Text'BOOL_OP;OR;COMPOSITE_TEST;<Unused>;TEST @Value(descriptivegroup) CONTAINS Structure'Structure Text'BOOL_OP;OR;COMPOSITE_TEST;<Unused>;TEST @Value(descriptivegroup) = Political Or Administrative'Administrative Text'BOOL_OP;AND;COMPOSITE_TEST;<Unused>;TEST @Value(descriptivegroup) = General Surface;TEST @Value(make) = Natural'General Surface Natural Text'BOOL_OP;COMPOSITE;COMPOSITE_TEST;1 AND 2 OR 3 AND 4;TEST @Value(descriptivegroup) = General Surface;TEST @Value(make) = Manmade;TEST @Value(descriptivegroup) = General Surface;TEST make ATTRIBUTE_VALUE_NULL _FME_BLANK_STRING_'General Surface Manmade Text'BOOL_OP;AND;COMPOSITE_TEST;<Unused>;TEST @Value(descriptivegroup) = Landform;TEST @Value(make) = Natural'Landform Natural Text'BOOL_OP;OR;COMPOSITE_TEST;<Unused>;TEST @Value(descriptiveterm) = Foreshore'Foreshore Text'BOOL_OP;OR;COMPOSITE_TEST;<Unused>;TEST @Value(descriptivegroup) CONTAINS Tidal Water'Tidal Water Text'BOOL_OP;OR;COMPOSITE_TEST;<Unused>;TEST @Value(descriptivegroup) = Built Environment'Built Environment Text'BOOL_OP;OR;COMPOSITE_TEST;<Unused>;TEST @Value(descriptivegroup) CONTAINS Historic Interest'Historic Text'BOOL_OP;OR;COMPOSITE_TEST;<Unused>;TEST @Value(descriptivegroup) = Rail'Rail Text'BOOL_OP;OR;COMPOSITE_TEST;<Unused>;TEST @Value(descriptivegroup) CONTAINS General Feature'General Feature Text'BOOL_OP;AND;COMPOSITE_TEST;<Unused>;TEST @Value(descriptivegroup) = Landform;TEST @Value(make) = Manmade'Landform Manmade Text'FME_NUM_CONDITIONS18___",style_code,"FME_CONDITIONAL:DEFAULT_VALUE'99'BOOL_OP;OR;COMPOSITE_TEST;<Unused>;TEST @Value(descriptivegroup) CONTAINS Buildings Or Structure'1'BOOL_OP;OR;COMPOSITE_TEST;<Unused>;TEST @Value(descriptivegroup) CONTAINS Inland Water'2'BOOL_OP;OR;COMPOSITE_TEST;<Unused>;TEST @Value(descriptivegroup) CONTAINS Road Or Track'3'BOOL_OP;OR;COMPOSITE_TEST;<Unused>;TEST @Value(descriptivegroup) = Terrain And Height'4'BOOL_OP;OR;COMPOSITE_TEST;<Unused>;TEST @Value(descriptivegroup) CONTAINS Roadside'5'BOOL_OP;OR;COMPOSITE_TEST;<Unused>;TEST @Value(descriptivegroup) CONTAINS Structure'6'BOOL_OP;OR;COMPOSITE_TEST;<Unused>;TEST @Value(descriptivegroup) = Political Or Administrative'7'BOOL_OP;AND;COMPOSITE_TEST;<Unused>;TEST @Value(descriptivegroup) = General Surface;TEST @Value(make) = Natural'8'BOOL_OP;COMPOSITE;COMPOSITE_TEST;1 AND 2 OR 3 AND 4;TEST @Value(descriptivegroup) = General Surface;TEST @Value(make) = Manmade;TEST @Value(descriptivegroup) = General Surface;TEST make ATTRIBUTE_VALUE_NULL _FME_BLANK_STRING_'9'BOOL_OP;AND;COMPOSITE_TEST;<Unused>;TEST @Value(descriptivegroup) = Landform;TEST @Value(make) = Natural'10'BOOL_OP;OR;COMPOSITE_TEST;<Unused>;TEST @Value(descriptiveterm) = Foreshore'11'BOOL_OP;OR;COMPOSITE_TEST;<Unused>;TEST @Value(descriptivegroup) CONTAINS Tidal Water'12'BOOL_OP;OR;COMPOSITE_TEST;<Unused>;TEST @Value(descriptivegroup) = Built Environment'13'BOOL_OP;OR;COMPOSITE_TEST;<Unused>;TEST @Value(descriptivegroup) CONTAINS Historic Interest'14'BOOL_OP;OR;COMPOSITE_TEST;<Unused>;TEST @Value(descriptivegroup) = Rail'15'BOOL_OP;OR;COMPOSITE_TEST;<Unused>;TEST @Value(descriptivegroup) CONTAINS General Feature'16'BOOL_OP;AND;COMPOSITE_TEST;<Unused>;TEST @Value(descriptivegroup) = Landform;TEST @Value(make) = Manmade'17'FME_NUM_CONDITIONS18___",colour_code,"FME_CONDITIONAL:DEFAULT_VALUE'1'BOOL_OP;OR;COMPOSITE_TEST;<Unused>;TEST @Value(descriptivegroup) CONTAINS Buildings Or Structure'1'BOOL_OP;OR;COMPOSITE_TEST;<Unused>;TEST @Value(descriptivegroup) CONTAINS Inland Water'2'BOOL_OP;OR;COMPOSITE_TEST;<Unused>;TEST @Value(descriptivegroup) CONTAINS Road Or Track'1'BOOL_OP;OR;COMPOSITE_TEST;<Unused>;TEST @Value(descriptivegroup) = Terrain And Height'3'BOOL_OP;OR;COMPOSITE_TEST;<Unused>;TEST @Value(descriptivegroup) CONTAINS Roadside'1'BOOL_OP;OR;COMPOSITE_TEST;<Unused>;TEST @Value(descriptivegroup) CONTAINS Structure'1'BOOL_OP;OR;COMPOSITE_TEST;<Unused>;TEST @Value(descriptivegroup) = Political Or Administrative'5'BOOL_OP;AND;COMPOSITE_TEST;<Unused>;TEST @Value(descriptivegroup) = General Surface;TEST @Value(make) = Natural'1'BOOL_OP;COMPOSITE;COMPOSITE_TEST;1 AND 2 OR 3 AND 4;TEST @Value(descriptivegroup) = General Surface;TEST @Value(make) = Manmade;TEST @Value(descriptivegroup) = General Surface;TEST make ATTRIBUTE_VALUE_NULL _FME_BLANK_STRING_'1'BOOL_OP;AND;COMPOSITE_TEST;<Unused>;TEST @Value(descriptivegroup) = Landform;TEST @Value(make) = Natural'4'BOOL_OP;OR;COMPOSITE_TEST;<Unused>;TEST @Value(descriptiveterm) = Foreshore'4'BOOL_OP;OR;COMPOSITE_TEST;<Unused>;TEST @Value(descriptivegroup) CONTAINS Tidal Water'2'BOOL_OP;OR;COMPOSITE_TEST;<Unused>;TEST @Value(descriptivegroup) = Built Environment'1'BOOL_OP;OR;COMPOSITE_TEST;<Unused>;TEST @Value(descriptivegroup) CONTAINS Historic Interest'1'BOOL_OP;OR;COMPOSITE_TEST;<Unused>;TEST @Value(descriptivegroup) = Rail'1'BOOL_OP;OR;COMPOSITE_TEST;<Unused>;TEST @Value(descriptivegroup) CONTAINS General Feature'1'BOOL_OP;AND;COMPOSITE_TEST;<Unused>;TEST @Value(descriptivegroup) = Landform;TEST @Value(make) = Manmade'4'FME_NUM_CONDITIONS18___",font_code,"FME_CONDITIONAL:DEFAULT_VALUE'1'BOOL_OP;OR;COMPOSITE_TEST;<Unused>;TEST @Value(descriptivegroup) CONTAINS Buildings Or Structure'1'BOOL_OP;OR;COMPOSITE_TEST;<Unused>;TEST @Value(descriptivegroup) CONTAINS Inland Water'2'BOOL_OP;OR;COMPOSITE_TEST;<Unused>;TEST @Value(descriptivegroup) CONTAINS Road Or Track'1'BOOL_OP;OR;COMPOSITE_TEST;<Unused>;TEST @Value(descriptivegroup) = Terrain And Height'1'BOOL_OP;OR;COMPOSITE_TEST;<Unused>;TEST @Value(descriptivegroup) CONTAINS Roadside'1'BOOL_OP;OR;COMPOSITE_TEST;<Unused>;TEST @Value(descriptivegroup) CONTAINS Structure'1'BOOL_OP;OR;COMPOSITE_TEST;<Unused>;TEST @Value(descriptivegroup) = Political Or Administrative'1'BOOL_OP;AND;COMPOSITE_TEST;<Unused>;TEST @Value(descriptivegroup) = General Surface;TEST @Value(make) = Natural'1'BOOL_OP;COMPOSITE;COMPOSITE_TEST;1 AND 2 OR 3 AND 4;TEST @Value(descriptivegroup) = General Surface;TEST @Value(make) = Manmade;TEST @Value(descriptivegroup) = General Surface;TEST make ATTRIBUTE_VALUE_NULL _FME_BLANK_STRING_'1'BOOL_OP;AND;COMPOSITE_TEST;<Unused>;TEST @Value(descriptivegroup) = Landform;TEST @Value(make) = Natural'1'BOOL_OP;OR;COMPOSITE_TEST;<Unused>;TEST @Value(descriptiveterm) = Foreshore'1'BOOL_OP;OR;COMPOSITE_TEST;<Unused>;TEST @Value(descriptivegroup) CONTAINS Tidal Water'2'BOOL_OP;OR;COMPOSITE_TEST;<Unused>;TEST @Value(descriptivegroup) = Built Environment'1'BOOL_OP;OR;COMPOSITE_TEST;<Unused>;TEST @Value(descriptivegroup) CONTAINS Historic Interest'3'BOOL_OP;OR;COMPOSITE_TEST;<Unused>;TEST @Value(descriptivegroup) = Rail'1'BOOL_OP;OR;COMPOSITE_TEST;<Unused>;TEST @Value(descriptivegroup) CONTAINS General Feature'1'BOOL_OP;AND;COMPOSITE_TEST;<Unused>;TEST @Value(descriptivegroup) = Landform;TEST @Value(make) = Manmade'1'FME_NUM_CONDITIONS18___",rotation,@Evaluate(@Value(orientation)/10),geo_x,"FME_CONDITIONAL:DEFAULT_VALUE'_FME_NO_OP_'BOOL_OP;OR;COMPOSITE_TEST;<Unused>;TEST @Value(anchorposition) = 0'0'BOOL_OP;OR;COMPOSITE_TEST;<Unused>;TEST @Value(anchorposition) = 1'0'BOOL_OP;OR;COMPOSITE_TEST;<Unused>;TEST @Value(anchorposition) = 2'0'BOOL_OP;OR;COMPOSITE_TEST;<Unused>;TEST @Value(anchorposition) = 3'0.5'BOOL_OP;OR;COMPOSITE_TEST;<Unused>;TEST @Value(anchorposition) = 4'0.5'BOOL_OP;OR;COMPOSITE_TEST;<Unused>;TEST @Value(anchorposition) = 5'0.5'BOOL_OP;OR;COMPOSITE_TEST;<Unused>;TEST @Value(anchorposition) = 6'1'BOOL_OP;OR;COMPOSITE_TEST;<Unused>;TEST @Value(anchorposition) = 7'1'BOOL_OP;OR;COMPOSITE_TEST;<Unused>;TEST @Value(anchorposition) = 8'1'FME_NUM_CONDITIONS10___",geo_y,"FME_CONDITIONAL:DEFAULT_VALUE'_FME_NO_OP_'BOOL_OP;OR;COMPOSITE_TEST;<Unused>;TEST @Value(anchorposition) = 0'0'BOOL_OP;OR;COMPOSITE_TEST;<Unused>;TEST @Value(anchorposition) = 1'0.5'BOOL_OP;OR;COMPOSITE_TEST;<Unused>;TEST @Value(anchorposition) = 2'1'BOOL_OP;OR;COMPOSITE_TEST;<Unused>;TEST @Value(anchorposition) = 3'0'BOOL_OP;OR;COMPOSITE_TEST;<Unused>;TEST @Value(anchorposition) = 4'0.5'BOOL_OP;OR;COMPOSITE_TEST;<Unused>;TEST @Value(anchorposition) = 5'1'BOOL_OP;OR;COMPOSITE_TEST;<Unused>;TEST @Value(anchorposition) = 6'0'BOOL_OP;OR;COMPOSITE_TEST;<Unused>;TEST @Value(anchorposition) = 7'0.5'BOOL_OP;OR;COMPOSITE_TEST;<Unused>;TEST @Value(anchorposition) = 8'1'FME_NUM_CONDITIONS10___",anchor,"FME_CONDITIONAL:DEFAULT_VALUE'_FME_NO_OP_'BOOL_OP;OR;COMPOSITE_TEST;<Unused>;TEST @Value(anchorposition) = 0'SW'BOOL_OP;OR;COMPOSITE_TEST;<Unused>;TEST @Value(anchorposition) = 1'W'BOOL_OP;OR;COMPOSITE_TEST;<Unused>;TEST @Value(anchorposition) = 2'NW'BOOL_OP;OR;COMPOSITE_TEST;<Unused>;TEST @Value(anchorposition) = 3'S'BOOL_OP;OR;COMPOSITE_TEST;<Unused>;TEST @Value(anchorposition) = 4''BOOL_OP;OR;COMPOSITE_TEST;<Unused>;TEST @Value(anchorposition) = 5'N'BOOL_OP;OR;COMPOSITE_TEST;<Unused>;TEST @Value(anchorposition) = 6'SE'BOOL_OP;OR;COMPOSITE_TEST;<Unused>;TEST @Value(anchorposition) = 7'E'BOOL_OP;OR;COMPOSITE_TEST;<Unused>;TEST @Value(anchorposition) = 8'NE'FME_NUM_CONDITIONS10___"
    -> CT_font_Styler
CT_font_Styler: AttributeCreator
    ATTR_LIST = fontname,"FME_CONDITIONAL:DEFAULT_VALUE'_FME_NO_OP_'BOOL_OP;OR;COMPOSITE_TEST;<Unused>;TEST @Value(font_code) = 1'Arial'BOOL_OP;OR;COMPOSITE_TEST;<Unused>;TEST @Value(font_code) = 2'Arial Italics'BOOL_OP;OR;COMPOSITE_TEST;<Unused>;TEST @Value(font_code) = 3'Times New Roman Italics'FME_NUM_CONDITIONS4___",fontcolour_hex,"FME_CONDITIONAL:DEFAULT_VALUE'_FME_NO_OP_'BOOL_OP;OR;COMPOSITE_TEST;<Unused>;TEST @Value(colour_code) = 1'#717171'BOOL_OP;OR;COMPOSITE_TEST;<Unused>;TEST @Value(colour_code) = 2'#25ADC9'BOOL_OP;OR;COMPOSITE_TEST;<Unused>;TEST @Value(colour_code) = 3'#A48F7A'BOOL_OP;OR;COMPOSITE_TEST;<Unused>;TEST @Value(colour_code) = 4'#7F7757'BOOL_OP;OR;COMPOSITE_TEST;<Unused>;TEST @Value(colour_code) = 5'#FF00FF'FME_NUM_CONDITIONS6___",fontcolour_rgb,"FME_CONDITIONAL:DEFAULT_VALUE'_FME_NO_OP_'BOOL_OP;OR;COMPOSITE_TEST;<Unused>;TEST @Value(colour_code) = 1'113,113,113'BOOL_OP;OR;COMPOSITE_TEST;<Unused>;TEST @Value(colour_code) = 2'37,173,201'BOOL_OP;OR;COMPOSITE_TEST;<Unused>;TEST @Value(colour_code) = 3'164,143,122'BOOL_OP;OR;COMPOSITE_TEST;<Unused>;TEST @Value(colour_code) = 4'127,119,87'BOOL_OP;OR;COMPOSITE_TEST;<Unused>;TEST @Value(colour_code) = 5'255,0,255'FME_NUM_CONDITIONS6___"
    -> Counter
TL_Style_Creator: AttributeCreator
    ATTR_LIST = style_description,"FME_CONDITIONAL:DEFAULT_VALUE'Unclassified'BOOL_OP;AND;COMPOSITE_TEST;<Unused>;TEST @Value(descriptivegroup) CONTAINS General Feature;TEST descriptiveterm ATTRIBUTE_VALUE_NULL _FME_BLANK_STRING_;TEST @Value(physicalpresence) = Obstructing'Default Line'BOOL_OP;AND;COMPOSITE_TEST;<Unused>;TEST @Value(descriptivegroup) CONTAINS Building;TEST @Value(descriptiveterm) = Outline;TEST @Value(make) = Manmade;TEST @Value(physicalpresence) = Obstructing'Building Outline Line'BOOL_OP;AND;COMPOSITE_TEST;<Unused>;TEST @Value(descriptivegroup) CONTAINS General Feature;TEST descriptiveterm ATTRIBUTE_VALUE_NULL _FME_BLANK_STRING_;TEST @Value(physicalpresence) = Edge / Limit'Edge Line'BOOL_OP;AND;COMPOSITE_TEST;<Unused>;TEST @Value(descriptivegroup) CONTAINS Road Or Track;TEST @Value(descriptiveterm) = Public;TEST @Value(make) = Manmade;TEST @Value(physicalpresence) = Edge / Limit'Road Or Track Line'BOOL_OP;AND;COMPOSITE_TEST;<Unused>;TEST @Value(descriptivegroup) CONTAINS Building;TEST @Value(descriptiveterm) = Division;TEST @Value(make) = Manmade;TEST @Value(physicalpresence) = Obstructing'Building Division Line'BOOL_OP;AND;COMPOSITE_TEST;<Unused>;TEST @Value(descriptiveterm) = Polygon Closing Link'Polygon Closing Line'BOOL_OP;AND;COMPOSITE_TEST;<Unused>;TEST @Value(descriptivegroup) CONTAINS Inland Water;TEST descriptiveterm ATTRIBUTE_VALUE_NULL _FME_BLANK_STRING_;TEST @Value(physicalpresence) = Edge / Limit'Inland Water Line'BOOL_OP;AND;COMPOSITE_TEST;<Unused>;TEST @Value(descriptiveterm) = Inferred Property Closing Link'Property Closing Line'BOOL_OP;AND;COMPOSITE_TEST;<Unused>;TEST @Value(descriptivegroup) CONTAINS General Surface;TEST descriptiveterm ATTRIBUTE_VALUE_NULL _FME_BLANK_STRING_;TEST @Value(make) = Natural;TEST @Value(physicalpresence) = Edge / Limit'General Surface Natural Line'BOOL_OP;AND;COMPOSITE_TEST;<Unused>;TEST @Value(descriptivegroup) CONTAINS Building;TEST @Value(descriptiveterm) = Outline;TEST @Value(make) = Manmade;TEST @Value(physicalpresence) = Overhead'Building Overhead Line'BOOL_OP;AND;COMPOSITE_TEST;<Unused>;TEST @Value(descriptiveterm) = Bottom Of Slope'Bottom Of Slope Line'BOOL_OP;AND;COMPOSITE_TEST;<Unused>;TEST @Value(descriptiveterm) = Top Of Slope'Top Of Slope Line'BOOL_OP;AND;COMPOSITE_TEST;<Unused>;TEST @Value(descriptiveterm) = Step'Step Line'BOOL_OP;AND;COMPOSITE_TEST;<Unused>;TEST @Value(descriptiveterm) = Unmade Path Alignment'Path Line'BOOL_OP;AND;COMPOSITE_TEST;<Unused>;TEST @Value(descriptiveterm) = Mean High Water (Springs)'Mean High Water Line'BOOL_OP;AND;COMPOSITE_TEST;<Unused>;TEST @Value(descriptiveterm) = Traffic Calming'Traffic Calming Line'BOOL_OP;AND;COMPOSITE_TEST;<Unused>;TEST @Value(descriptiveterm) = Standard Gauge Track'Standard Gauge Track Line'BOOL_OP;AND;COMPOSITE_TEST;<Unused>;TEST @Value(descriptiveterm) = Bottom Of Cliff'Bottom Of Cliff Line'BOOL_OP;AND;COMPOSITE_TEST;<Unused>;TEST @Value(descriptiveterm) = Top Of Cliff'Top Of Cliff Line'BOOL_OP;AND;COMPOSITE_TEST;<Unused>;TEST @Value(descriptiveterm) = Mean Low Water (Springs)'Mean Low Water Line'BOOL_OP;AND;COMPOSITE_TEST;<Unused>;TEST @Value(descriptiveterm) = Overhead Construction'Overhead Construction Line'BOOL_OP;AND;COMPOSITE_TEST;<Unused>;TEST @Value(descriptiveterm) = Culvert'Culvert Line'BOOL_OP;AND;COMPOSITE_TEST;<Unused>;TEST @Value(descriptiveterm) = Pylon'Pylon Line'BOOL_OP;AND;COMPOSITE_TEST;<Unused>;TEST @Value(descriptivegroup) = Landform;TEST @Value(make) = Natural'Landform Natural Line'BOOL_OP;AND;COMPOSITE_TEST;<Unused>;TEST @Value(descriptiveterm) = Ridge Or Rock Line'Ridge Or Rock Line'BOOL_OP;AND;COMPOSITE_TEST;<Unused>;TEST @Value(descriptivegroup) = Historic Interest'Historic Interest Line'BOOL_OP;AND;COMPOSITE_TEST;<Unused>;TEST @Value(descriptiveterm) = Narrow Gauge'Narrow Gauge Line'BOOL_OP;AND;COMPOSITE_TEST;<Unused>;TEST @Value(descriptiveterm) = Buffer'Railway Buffer Line'BOOL_OP;AND;COMPOSITE_TEST;<Unused>;TEST @Value(descriptiveterm) = Tunnel Edge'Tunnel Edge Line'BOOL_OP;AND;COMPOSITE_TEST;<Unused>;TEST @Value(descriptivegroup) = Landform;TEST @Value(make) = Manmade'Landform Manmade Line'FME_NUM_CONDITIONS31___",style_code,"FME_CONDITIONAL:DEFAULT_VALUE'Unclassified'BOOL_OP;AND;COMPOSITE_TEST;<Unused>;TEST @Value(descriptivegroup) CONTAINS General Feature;TEST descriptiveterm ATTRIBUTE_VALUE_NULL _FME_BLANK_STRING_;TEST @Value(physicalpresence) = Obstructing'1'BOOL_OP;AND;COMPOSITE_TEST;<Unused>;TEST @Value(descriptivegroup) CONTAINS Building;TEST @Value(descriptiveterm) = Outline;TEST @Value(make) = Manmade;TEST @Value(physicalpresence) = Obstructing'2'BOOL_OP;AND;COMPOSITE_TEST;<Unused>;TEST @Value(descriptivegroup) CONTAINS General Feature;TEST descriptiveterm ATTRIBUTE_VALUE_NULL _FME_BLANK_STRING_;TEST @Value(physicalpresence) = Edge / Limit'3'BOOL_OP;AND;COMPOSITE_TEST;<Unused>;TEST @Value(descriptivegroup) CONTAINS Road Or Track;TEST @Value(descriptiveterm) = Public;TEST @Value(make) = Manmade;TEST @Value(physicalpresence) = Edge / Limit'4'BOOL_OP;AND;COMPOSITE_TEST;<Unused>;TEST @Value(descriptivegroup) CONTAINS Building;TEST @Value(descriptiveterm) = Division;TEST @Value(make) = Manmade;TEST @Value(physicalpresence) = Obstructing'5'BOOL_OP;AND;COMPOSITE_TEST;<Unused>;TEST @Value(descriptiveterm) = Polygon Closing Link'6'BOOL_OP;AND;COMPOSITE_TEST;<Unused>;TEST @Value(descriptivegroup) CONTAINS Inland Water;TEST descriptiveterm ATTRIBUTE_VALUE_NULL _FME_BLANK_STRING_;TEST @Value(physicalpresence) = Edge / Limit'7'BOOL_OP;AND;COMPOSITE_TEST;<Unused>;TEST @Value(descriptiveterm) = Inferred Property Closing Link'8'BOOL_OP;AND;COMPOSITE_TEST;<Unused>;TEST @Value(descriptivegroup) CONTAINS General Surface;TEST descriptiveterm ATTRIBUTE_VALUE_NULL _FME_BLANK_STRING_;TEST @Value(make) = Natural;TEST @Value(physicalpresence) = Edge / Limit'9'BOOL_OP;AND;COMPOSITE_TEST;<Unused>;TEST @Value(descriptivegroup) CONTAINS Building;TEST @Value(descriptiveterm) = Outline;TEST @Value(make) = Manmade;TEST @Value(physicalpresence) = Overhead'10'BOOL_OP;AND;COMPOSITE_TEST;<Unused>;TEST @Value(descriptiveterm) = Bottom Of Slope'11'BOOL_OP;AND;COMPOSITE_TEST;<Unused>;TEST @Value(descriptiveterm) = Top Of Slope'12'BOOL_OP;AND;COMPOSITE_TEST;<Unused>;TEST @Value(descriptiveterm) = Step'13'BOOL_OP;AND;COMPOSITE_TEST;<Unused>;TEST @Value(descriptiveterm) = Unmade Path Alignment'14'BOOL_OP;AND;COMPOSITE_TEST;<Unused>;TEST @Value(descriptiveterm) = Mean High Water (Springs)'15'BOOL_OP;AND;COMPOSITE_TEST;<Unused>;TEST @Value(descriptiveterm) = Traffic Calming'16'BOOL_OP;AND;COMPOSITE_TEST;<Unused>;TEST @Value(descriptiveterm) = Standard Gauge Track'17'BOOL_OP;AND;COMPOSITE_TEST;<Unused>;TEST @Value(descriptiveterm) = Bottom Of Cliff'18'BOOL_OP;AND;COMPOSITE_TEST;<Unused>;TEST @Value(descriptiveterm) = Top Of Cliff'19'BOOL_OP;AND;COMPOSITE_TEST;<Unused>;TEST @Value(descriptiveterm) = Mean Low Water (Springs)'20'BOOL_OP;AND;COMPOSITE_TEST;<Unused>;TEST @Value(descriptiveterm) = Overhead Construction'21'BOOL_OP;AND;COMPOSITE_TEST;<Unused>;TEST @Value(descriptiveterm) = Culvert'22'BOOL_OP;AND;COMPOSITE_TEST;<Unused>;TEST @Value(descriptiveterm) = Pylon'23'BOOL_OP;AND;COMPOSITE_TEST;<Unused>;TEST @Value(descriptivegroup) = Landform;TEST @Value(make) = Natural'24'BOOL_OP;AND;COMPOSITE_TEST;<Unused>;TEST @Value(descriptiveterm) = Ridge Or Rock Line'25'BOOL_OP;AND;COMPOSITE_TEST;<Unused>;TEST @Value(descriptivegroup) = Historic Interest'26'BOOL_OP;AND;COMPOSITE_TEST;<Unused>;TEST @Value(descriptiveterm) = Narrow Gauge'27'BOOL_OP;AND;COMPOSITE_TEST;<Unused>;TEST @Value(descriptiveterm) = Buffer'28'BOOL_OP;AND;COMPOSITE_TEST;<Unused>;TEST @Value(descriptiveterm) = Tunnel Edge'29'BOOL_OP;AND;COMPOSITE_TEST;<Unused>;TEST @Value(descriptivegroup) = Landform;TEST @Value(make) = Manmade'30'FME_NUM_CONDITIONS31___"
    -> Counter_6
TA_Style_Creator: AttributeCreator
    ATTR_LIST = style_code,"FME_CONDITIONAL:DEFAULT_VALUE'99'BOOL_OP;AND;COMPOSITE_TEST;<Unused>;TEST @Value(descriptivegroup) CONTAINS Building;TEST descriptiveterm ATTRIBUTE_VALUE_NULL _FME_BLANK_STRING_'1'BOOL_OP;AND;COMPOSITE_TEST;<Unused>;TEST @Value(descriptivegroup) CONTAINS General Surface;TEST @Value(descriptiveterm) = Multi Surface'2'BOOL_OP;AND;COMPOSITE_TEST;<Unused>;TEST @Value(descriptivegroup) CONTAINS General Surface;TEST descriptiveterm ATTRIBUTE_VALUE_NULL _FME_BLANK_STRING_;TEST @Value(make) = Natural'3'BOOL_OP;AND;COMPOSITE_TEST;<Unused>;TEST @Value(descriptivegroup) CONTAINS Road Or Track;TEST descriptiveterm ATTRIBUTE_VALUE_NULL _FME_BLANK_STRING_;TEST @Value(make) = Manmade'4'BOOL_OP;COMPOSITE;COMPOSITE_TEST;1 AND 2 AND 3 OR 4;TEST @Value(descriptivegroup) CONTAINS General Surface;TEST descriptiveterm ATTRIBUTE_VALUE_NULL _FME_BLANK_STRING_;TEST @Value(make) = Manmade;TEST @Value(make) = Unknown'5'BOOL_OP;AND;COMPOSITE_TEST;<Unused>;TEST @Value(descriptivegroup) CONTAINS Roadside;TEST @Value(make) = Natural'6'BOOL_OP;COMPOSITE;COMPOSITE_TEST;1 AND 2 OR 3;TEST @Value(descriptivegroup) CONTAINS Roadside;TEST @Value(make) = Manmade;TEST @Value(make) = Unknown'7'BOOL_OP;AND;COMPOSITE_TEST;<Unused>;TEST @Value(descriptivegroup) CONTAINS Inland Water;TEST descriptiveterm ATTRIBUTE_VALUE_NULL _FME_BLANK_STRING_'8'BOOL_OP;AND;COMPOSITE_TEST;<Unused>;TEST @Value(descriptivegroup) CONTAINS Path;TEST descriptiveterm ATTRIBUTE_VALUE_NULL _FME_BLANK_STRING_'9'BOOL_OP;AND;COMPOSITE_TEST;<Unused>;TEST @Value(descriptivegroup) CONTAINS Road Or Track;TEST @Value(descriptiveterm) = Track'10'BOOL_OP;AND;COMPOSITE_TEST;<Unused>;TEST @Value(descriptiveterm) = Slope'11'BOOL_OP;COMPOSITE;COMPOSITE_TEST;1 AND 2 OR 3 OR 4;TEST @Value(descriptivegroup) CONTAINS Structure;TEST descriptiveterm ATTRIBUTE_VALUE_NULL _FME_BLANK_STRING_;TEST @Value(descriptiveterm) = Upper Level Of Communication;TEST @Value(descriptiveterm) = Overhead Construction'12'BOOL_OP;AND;COMPOSITE_TEST;<Unused>;TEST @Value(descriptiveterm) = Cliff'13'BOOL_OP;AND;COMPOSITE_TEST;<Unused>;TEST @Value(descriptiveterm) = Step'14'BOOL_OP;AND;COMPOSITE_TEST;<Unused>;TEST @Value(descriptiveterm) = Foreshore'15'BOOL_OP;AND;COMPOSITE_TEST;<Unused>;TEST @Value(descriptiveterm) = Traffic Calming'16'BOOL_OP;AND;COMPOSITE_TEST;<Unused>;TEST @Value(descriptivegroup) = Glasshouse'17'BOOL_OP;AND;COMPOSITE_TEST;<Unused>;TEST @Value(descriptivegroup) CONTAINS Rail;TEST descriptiveterm ATTRIBUTE_VALUE_NULL _FME_BLANK_STRING_;TEST @Value(make) = Natural'18'BOOL_OP;AND;COMPOSITE_TEST;<Unused>;TEST @Value(descriptiveterm) = Pylon'19'BOOL_OP;AND;COMPOSITE_TEST;<Unused>;TEST @Value(descriptivegroup) CONTAINS Building;TEST @Value(descriptiveterm) = Archway'20'BOOL_OP;AND;COMPOSITE_TEST;<Unused>;TEST @Value(descriptivegroup) CONTAINS Landform;TEST @Value(make) = Natural'21'BOOL_OP;AND;COMPOSITE_TEST;<Unused>;TEST @Value(descriptivegroup) CONTAINS Tidal Water;TEST descriptiveterm ATTRIBUTE_VALUE_NULL _FME_BLANK_STRING_'22'BOOL_OP;AND;COMPOSITE_TEST;<Unused>;TEST @Value(descriptivegroup) CONTAINS Landform;TEST @Value(make) = Manmade'23'BOOL_OP;COMPOSITE;COMPOSITE_TEST;1 AND 2 OR 3;TEST @Value(descriptivegroup) = Rail;TEST @Value(make) = Manmade;TEST @Value(make) = Unknown'24'BOOL_OP;COMPOSITE;COMPOSITE_TEST;1 OR 2 AND 3 OR 4;TEST @Value(descriptiveterm) CONTAINS Nonconiferous Trees;TEST @Value(descriptiveterm) CONTAINS Nonconiferous Trees (Scattered);TEST @Value(descriptiveterm) CONTAINS Coniferous Trees;TEST @Value(descriptiveterm) CONTAINS Coniferous Trees (Scattered)'25'BOOL_OP;OR;COMPOSITE_TEST;<Unused>;TEST @Value(descriptiveterm) CONTAINS Nonconiferous Trees;TEST @Value(descriptiveterm) CONTAINS Nonconiferous Trees (Scattered)'26'BOOL_OP;OR;COMPOSITE_TEST;<Unused>;TEST @Value(descriptiveterm) CONTAINS Coniferous Trees;TEST @Value(descriptiveterm) CONTAINS Coniferous Trees (Scattered)'27'BOOL_OP;OR;COMPOSITE_TEST;<Unused>;TEST @Value(descriptiveterm) CONTAINS Orchard'28'BOOL_OP;OR;COMPOSITE_TEST;<Unused>;TEST @Value(descriptiveterm) CONTAINS Coppice Or Osiers'29'BOOL_OP;OR;COMPOSITE_TEST;<Unused>;TEST @Value(descriptiveterm) CONTAINS Scrub'30'BOOL_OP;OR;COMPOSITE_TEST;<Unused>;TEST @Value(descriptiveterm) CONTAINS Boulders;TEST @Value(descriptiveterm) CONTAINS Boulders (Scattered)'31'BOOL_OP;OR;COMPOSITE_TEST;<Unused>;TEST @Value(descriptiveterm) CONTAINS Rock;TEST @Value(descriptiveterm) CONTAINS Rock (Scattered)'32'BOOL_OP;OR;COMPOSITE_TEST;<Unused>;TEST @Value(descriptiveterm) CONTAINS Scree'33'BOOL_OP;OR;COMPOSITE_TEST;<Unused>;TEST @Value(descriptiveterm) CONTAINS Rough Grassland'34'BOOL_OP;OR;COMPOSITE_TEST;<Unused>;TEST @Value(descriptiveterm) CONTAINS Heath'35'BOOL_OP;OR;COMPOSITE_TEST;<Unused>;TEST @Value(descriptiveterm) CONTAINS Marsh Reeds Or Saltmarsh'36'FME_NUM_CONDITIONS37___",style_description,"FME_CONDITIONAL:DEFAULT_VALUE'Unclassified'BOOL_OP;AND;COMPOSITE_TEST;<Unused>;TEST @Value(descriptivegroup) CONTAINS Building;TEST descriptiveterm ATTRIBUTE_VALUE_NULL _FME_BLANK_STRING_'Building Fill'BOOL_OP;AND;COMPOSITE_TEST;<Unused>;TEST @Value(descriptivegroup) CONTAINS General Surface;TEST @Value(descriptiveterm) = Multi Surface'Multi Surface Fill'BOOL_OP;AND;COMPOSITE_TEST;<Unused>;TEST @Value(descriptivegroup) CONTAINS General Surface;TEST descriptiveterm ATTRIBUTE_VALUE_NULL _FME_BLANK_STRING_;TEST @Value(make) = Natural'Natural Fill'BOOL_OP;AND;COMPOSITE_TEST;<Unused>;TEST @Value(descriptivegroup) CONTAINS Road Or Track;TEST descriptiveterm ATTRIBUTE_VALUE_NULL _FME_BLANK_STRING_;TEST @Value(make) = Manmade'Road Or Track Fill'BOOL_OP;COMPOSITE;COMPOSITE_TEST;1 AND 2 AND 3 OR 4;TEST @Value(descriptivegroup) CONTAINS General Surface;TEST descriptiveterm ATTRIBUTE_VALUE_NULL _FME_BLANK_STRING_;TEST @Value(make) = Manmade;TEST @Value(make) = Unknown'Manmade Fill'BOOL_OP;AND;COMPOSITE_TEST;<Unused>;TEST @Value(descriptivegroup) CONTAINS Roadside;TEST @Value(make) = Natural'Roadside Natural Fill'BOOL_OP;COMPOSITE;COMPOSITE_TEST;1 AND 2 OR 3;TEST @Value(descriptivegroup) CONTAINS Roadside;TEST @Value(make) = Manmade;TEST @Value(make) = Unknown'Roadside Manmade Fill'BOOL_OP;AND;COMPOSITE_TEST;<Unused>;TEST @Value(descriptivegroup) CONTAINS Inland Water;TEST descriptiveterm ATTRIBUTE_VALUE_NULL _FME_BLANK_STRING_'Inland Water Fill'BOOL_OP;AND;COMPOSITE_TEST;<Unused>;TEST @Value(descriptivegroup) CONTAINS Path;TEST descriptiveterm ATTRIBUTE_VALUE_NULL _FME_BLANK_STRING_'Path Fill'BOOL_OP;AND;COMPOSITE_TEST;<Unused>;TEST @Value(descriptivegroup) CONTAINS Road Or Track;TEST @Value(descriptiveterm) = Track'Track Fill'BOOL_OP;AND;COMPOSITE_TEST;<Unused>;TEST @Value(descriptiveterm) = Slope'Slope Fill'BOOL_OP;COMPOSITE;COMPOSITE_TEST;1 AND 2 OR 3 OR 4;TEST @Value(descriptivegroup) CONTAINS Structure;TEST descriptiveterm ATTRIBUTE_VALUE_NULL _FME_BLANK_STRING_;TEST @Value(descriptiveterm) = Upper Level Of Communication;TEST @Value(descriptiveterm) = Overhead Construction'Structure Fill'BOOL_OP;AND;COMPOSITE_TEST;<Unused>;TEST @Value(descriptiveterm) = Cliff'Cliff Fill'BOOL_OP;AND;COMPOSITE_TEST;<Unused>;TEST @Value(descriptiveterm) = Step'Step Fill'BOOL_OP;AND;COMPOSITE_TEST;<Unused>;TEST @Value(descriptiveterm) = Foreshore'Foreshore Fill'BOOL_OP;AND;COMPOSITE_TEST;<Unused>;TEST @Value(descriptiveterm) = Traffic Calming'Traffic Calming Fill'BOOL_OP;AND;COMPOSITE_TEST;<Unused>;TEST @Value(descriptivegroup) = Glasshouse'Glasshouse Fill'BOOL_OP;AND;COMPOSITE_TEST;<Unused>;TEST @Value(descriptivegroup) CONTAINS Rail;TEST descriptiveterm ATTRIBUTE_VALUE_NULL _FME_BLANK_STRING_;TEST @Value(make) = Natural'Rail Natural Fill'BOOL_OP;AND;COMPOSITE_TEST;<Unused>;TEST @Value(descriptiveterm) = Pylon'Pylon Fill'BOOL_OP;AND;COMPOSITE_TEST;<Unused>;TEST @Value(descriptivegroup) CONTAINS Building;TEST @Value(descriptiveterm) = Archway'Archway Fill'BOOL_OP;AND;COMPOSITE_TEST;<Unused>;TEST @Value(descriptivegroup) CONTAINS Landform;TEST @Value(make) = Natural'Landform Natural Fill'BOOL_OP;AND;COMPOSITE_TEST;<Unused>;TEST @Value(descriptivegroup) CONTAINS Tidal Water;TEST descriptiveterm ATTRIBUTE_VALUE_NULL _FME_BLANK_STRING_'Tidal Water Fill'BOOL_OP;AND;COMPOSITE_TEST;<Unused>;TEST @Value(descriptivegroup) CONTAINS Landform;TEST @Value(make) = Manmade'Landform Manmade Fill'BOOL_OP;COMPOSITE;COMPOSITE_TEST;1 AND 2 OR 3;TEST @Value(descriptivegroup) = Rail;TEST @Value(make) = Manmade;TEST @Value(make) = Unknown'Rail Manmade Fill'BOOL_OP;COMPOSITE;COMPOSITE_TEST;1 OR 2 AND 3 OR 4;TEST @Value(descriptiveterm) CONTAINS Nonconiferous Trees;TEST @Value(descriptiveterm) CONTAINS Nonconiferous Trees (Scattered);TEST @Value(descriptiveterm) CONTAINS Coniferous Trees;TEST @Value(descriptiveterm) CONTAINS Coniferous Trees (Scattered)'Mixed Woodland Fill'BOOL_OP;OR;COMPOSITE_TEST;<Unused>;TEST @Value(descriptiveterm) CONTAINS Nonconiferous Trees;TEST @Value(descriptiveterm) CONTAINS Nonconiferous Trees (Scattered)'Nonconiferous Woodland Fill'BOOL_OP;OR;COMPOSITE_TEST;<Unused>;TEST @Value(descriptiveterm) CONTAINS Coniferous Trees;TEST @Value(descriptiveterm) CONTAINS Coniferous Trees (Scattered)'Coniferous Woodland Fill'BOOL_OP;OR;COMPOSITE_TEST;<Unused>;TEST @Value(descriptiveterm) CONTAINS Orchard'Orchard Fill'BOOL_OP;OR;COMPOSITE_TEST;<Unused>;TEST @Value(descriptiveterm) CONTAINS Coppice Or Osiers'Coppice Or Osiers Fill'BOOL_OP;OR;COMPOSITE_TEST;<Unused>;TEST @Value(descriptiveterm) CONTAINS Scrub'Scrub Fill'BOOL_OP;OR;COMPOSITE_TEST;<Unused>;TEST @Value(descriptiveterm) CONTAINS Boulders;TEST @Value(descriptiveterm) CONTAINS Boulders (Scattered)'Boulders Fill'BOOL_OP;OR;COMPOSITE_TEST;<Unused>;TEST @Value(descriptiveterm) CONTAINS Rock;TEST @Value(descriptiveterm) CONTAINS Rock (Scattered)'Rock Fill'BOOL_OP;OR;COMPOSITE_TEST;<Unused>;TEST @Value(descriptiveterm) CONTAINS Scree'Scree Fill'BOOL_OP;OR;COMPOSITE_TEST;<Unused>;TEST @Value(descriptiveterm) CONTAINS Rough Grassland'Rough Grassland Fill'BOOL_OP;OR;COMPOSITE_TEST;<Unused>;TEST @Value(descriptiveterm) CONTAINS Heath'Heath Fill'BOOL_OP;OR;COMPOSITE_TEST;<Unused>;TEST @Value(descriptiveterm) CONTAINS Marsh Reeds Or Saltmarsh'Marsh Fill'FME_NUM_CONDITIONS37___"
    -> Counter_2
CS_Style_Creator: AttributeCreator
    ATTR_LIST = style_code,"FME_CONDITIONAL:DEFAULT_VALUE'99'BOOL_OP;OR;COMPOSITE_TEST;<Unused>;TEST @Value(featurecode) = 10091'1'BOOL_OP;OR;COMPOSITE_TEST;<Unused>;TEST @Value(featurecode) = 10082'2'BOOL_OP;OR;COMPOSITE_TEST;<Unused>;TEST @Value(featurecode) = 10130'3'BOOL_OP;OR;COMPOSITE_TEST;<Unused>;TEST @Value(featurecode) = 10066;TEST @Value(featurecode) = 10170'4'BOOL_OP;OR;COMPOSITE_TEST;<Unused>;TEST @Value(featurecode) = 10165'5'BOOL_OP;OR;COMPOSITE_TEST;<Unused>;TEST @Value(featurecode) = 10177'6'FME_NUM_CONDITIONS7___",style_description,"FME_CONDITIONAL:DEFAULT_VALUE'Unclassified'BOOL_OP;OR;COMPOSITE_TEST;<Unused>;TEST @Value(featurecode) = 10091'Culvert Symbol'BOOL_OP;OR;COMPOSITE_TEST;<Unused>;TEST @Value(featurecode) = 10082'Direction Of Flow Symbol'BOOL_OP;OR;COMPOSITE_TEST;<Unused>;TEST @Value(featurecode) = 10130'Boundary Half Mereing Symbol'BOOL_OP;OR;COMPOSITE_TEST;<Unused>;TEST @Value(featurecode) = 10066;TEST @Value(featurecode) = 10170'Bench Mark Symbol'BOOL_OP;OR;COMPOSITE_TEST;<Unused>;TEST @Value(featurecode) = 10165'Railway Switch Symbol'BOOL_OP;OR;COMPOSITE_TEST;<Unused>;TEST @Value(featurecode) = 10177'Road Related Flow Symbol'FME_NUM_CONDITIONS7___"
    -> Counter_3
BL_Style_Creator: AttributeCreator
    ATTR_LIST = style_code,"FME_CONDITIONAL:DEFAULT_VALUE'99'BOOL_OP;OR;COMPOSITE_TEST;<Unused>;TEST @Value(featurecode) = 10136'1'BOOL_OP;OR;COMPOSITE_TEST;<Unused>;TEST @Value(featurecode) = 10131'2'BOOL_OP;OR;COMPOSITE_TEST;<Unused>;TEST @Value(featurecode) = 10128'3'BOOL_OP;OR;COMPOSITE_TEST;<Unused>;TEST @Value(featurecode) = 10127'4'BOOL_OP;OR;COMPOSITE_TEST;<Unused>;TEST @Value(featurecode) = 10135'5'FME_NUM_CONDITIONS6___",style_description,"FME_CONDITIONAL:DEFAULT_VALUE'Unclassified'BOOL_OP;OR;COMPOSITE_TEST;<Unused>;TEST @Value(featurecode) = 10136'Parish Boundary'BOOL_OP;OR;COMPOSITE_TEST;<Unused>;TEST @Value(featurecode) = 10131'District Boundary'BOOL_OP;OR;COMPOSITE_TEST;<Unused>;TEST @Value(featurecode) = 10128'Electoral Boundary'BOOL_OP;OR;COMPOSITE_TEST;<Unused>;TEST @Value(featurecode) = 10127'County Boundary'BOOL_OP;OR;COMPOSITE_TEST;<Unused>;TEST @Value(featurecode) = 10135'Parliamentary Boundary'FME_NUM_CONDITIONS6___"
    -> Counter_4
TP_Style_Creator: AttributeCreator
    ATTR_LIST = style_description,"FME_CONDITIONAL:DEFAULT_VALUE'Unclassified'BOOL_OP;OR;COMPOSITE_TEST;<Unused>;TEST @Value(featurecode) = 10197'Spot Height Point'BOOL_OP;OR;COMPOSITE_TEST;<Unused>;TEST @Value(featurecode) = 10085'Culvert Point'BOOL_OP;COMPOSITE;COMPOSITE_TEST;1 OR 2 OR 3 AND 4;TEST @Value(featurecode) = 10048;TEST @Value(featurecode) = 10132;TEST @Value(featurecode) = 10080;TEST @Value(descriptiveterm) = Positioned Nonconiferous Tree'Positioned Nonconiferous Tree Point'BOOL_OP;OR;COMPOSITE_TEST;<Unused>;TEST @Value(featurecode) = 10088'Inland Water Point'BOOL_OP;AND;COMPOSITE_TEST;<Unused>;TEST @Value(featurecode) = 10186;TEST descriptiveterm ATTRIBUTE_VALUE_NULL _FME_BLANK_STRING_'Structure Point'BOOL_OP;AND;COMPOSITE_TEST;<Unused>;TEST @Value(featurecode) = 10179'Roadside Point'BOOL_OP;AND;COMPOSITE_TEST;<Unused>;TEST @Value(featurecode) = 10186;TEST @Value(descriptiveterm) = Overhead Construction'Overhead Construction Point'BOOL_OP;AND;COMPOSITE_TEST;<Unused>;TEST @Value(featurecode) = 10158'Rail Point'BOOL_OP;AND;COMPOSITE_TEST;<Unused>;TEST @Value(featurecode) = 10050'Positioned Coniferous Point'BOOL_OP;AND;COMPOSITE_TEST;<Unused>;TEST @Value(featurecode) = 10094'Landform Point'BOOL_OP;AND;COMPOSITE_TEST;<Unused>;TEST @Value(featurecode) = 10080;TEST @Value(descriptiveterm) = Structure'Historic Point'BOOL_OP;AND;COMPOSITE_TEST;<Unused>;TEST @Value(featurecode) = 10129'Boundary Post Point'BOOL_OP;AND;COMPOSITE_TEST;<Unused>;TEST @Value(featurecode) = 10186;TEST @Value(descriptiveterm) = Triangulation Point Or Pillar'Triangulation Point Or Pillar Point'BOOL_OP;AND;COMPOSITE_TEST;<Unused>;TEST @Value(featurecode) = 10191'Structure Point'BOOL_OP;AND;COMPOSITE_TEST;<Unused>;TEST @Value(featurecode) = 10072'Site Of Heritage'BOOL_OP;AND;COMPOSITE_TEST;<Unused>;TEST @Value(featurecode) = 10051'Positioned Boulder Point'BOOL_OP;AND;COMPOSITE_TEST;<Unused>;TEST @Value(featurecode) = 10209'Tidal Water Point'BOOL_OP;AND;COMPOSITE_TEST;<Unused>;TEST @Value(featurecode) = 10100'Disused Feature Point'BOOL_OP;AND;COMPOSITE_TEST;<Unused>;TEST @Value(featurecode) = 10159;TEST @Value(descriptiveterm) = Switch'Rail Switch Point'BOOL_OP;COMPOSITE;COMPOSITE_TEST;1 OR 2 OR 3;TEST @Value(featurecode) = 10120;TEST @Value(featurecode) = 10176;TEST @Value(featurecode) = 10159'Inland Water Point'BOOL_OP;OR;COMPOSITE_TEST;<Unused>;TEST @Value(featurecode) = 10159'Inland Water Point'FME_NUM_CONDITIONS22___",style_code,"FME_CONDITIONAL:DEFAULT_VALUE'99'BOOL_OP;OR;COMPOSITE_TEST;<Unused>;TEST @Value(featurecode) = 10197'1'BOOL_OP;OR;COMPOSITE_TEST;<Unused>;TEST @Value(featurecode) = 10085'2'BOOL_OP;COMPOSITE;COMPOSITE_TEST;1 OR 2 OR 3 AND 4;TEST @Value(featurecode) = 10048;TEST @Value(featurecode) = 10132;TEST @Value(featurecode) = 10080;TEST @Value(descriptiveterm) = Positioned Nonconiferous Tree'3'BOOL_OP;OR;COMPOSITE_TEST;<Unused>;TEST @Value(featurecode) = 10088'4'BOOL_OP;AND;COMPOSITE_TEST;<Unused>;TEST @Value(featurecode) = 10186;TEST descriptiveterm ATTRIBUTE_VALUE_NULL _FME_BLANK_STRING_'5'BOOL_OP;AND;COMPOSITE_TEST;<Unused>;TEST @Value(featurecode) = 10179'6'BOOL_OP;AND;COMPOSITE_TEST;<Unused>;TEST @Value(featurecode) = 10186;TEST @Value(descriptiveterm) = Overhead Construction'7'BOOL_OP;AND;COMPOSITE_TEST;<Unused>;TEST @Value(featurecode) = 10158'8'BOOL_OP;AND;COMPOSITE_TEST;<Unused>;TEST @Value(featurecode) = 10050'9'BOOL_OP;AND;COMPOSITE_TEST;<Unused>;TEST @Value(featurecode) = 10094'10'BOOL_OP;AND;COMPOSITE_TEST;<Unused>;TEST @Value(featurecode) = 10080;TEST @Value(descriptiveterm) = Structure'11'BOOL_OP;AND;COMPOSITE_TEST;<Unused>;TEST @Value(featurecode) = 10129'12'BOOL_OP;AND;COMPOSITE_TEST;<Unused>;TEST @Value(featurecode) = 10186;TEST @Value(descriptiveterm) = Triangulation Point Or Pillar'13'BOOL_OP;AND;COMPOSITE_TEST;<Unused>;TEST @Value(featurecode) = 10191'5'BOOL_OP;AND;COMPOSITE_TEST;<Unused>;TEST @Value(featurecode) = 10072'14'BOOL_OP;AND;COMPOSITE_TEST;<Unused>;TEST @Value(featurecode) = 10051'15'BOOL_OP;AND;COMPOSITE_TEST;<Unused>;TEST @Value(featurecode) = 10209'16'BOOL_OP;AND;COMPOSITE_TEST;<Unused>;TEST @Value(featurecode) = 10100'17'BOOL_OP;AND;COMPOSITE_TEST;<Unused>;TEST @Value(featurecode) = 10159;TEST @Value(descriptiveterm) = Switch'18'BOOL_OP;COMPOSITE;COMPOSITE_TEST;1 OR 2 OR 3;TEST @Value(featurecode) = 10120;TEST @Value(featurecode) = 10176;TEST @Value(featurecode) = 10159'4'FME_NUM_CONDITIONS21___"
    -> Counter_5

Bookmark: Generate primary key
Note: Genterates a primary key for use in PostGIS
Counter
    START = 1
    SCOPE = Local
    DOMAIN = counter
    CNT_ATTR = ogc_fid
    -> $(Schema).cartographictext (writer POSTGIS_1)
Counter_6
    START = 1
    SCOPE = Local
    DOMAIN = counter
    CNT_ATTR = ogc_fid
    -> $(Schema).topographicline (writer POSTGIS_1)
Counter_2
    START = 1
    SCOPE = Local
    DOMAIN = counter
    CNT_ATTR = ogc_fid
    -> $(Schema).topographicarea (writer POSTGIS_1)
Counter_3
    START = 1
    SCOPE = Local
    DOMAIN = counter
    CNT_ATTR = ogc_fid
    -> $(Schema).cartographicsymbol (writer POSTGIS_1)
Counter_4
    START = 1
    SCOPE = Local
    DOMAIN = counter
    CNT_ATTR = ogc_fid
    -> $(Schema).boundaryline (writer POSTGIS_1)
Counter_5
    START = 1
    SCOPE = Local
    DOMAIN = counter
    CNT_ATTR = ogc_fid
    -> $(Schema).topographicpoint (writer POSTGIS_1)
Counter_7
    START = 1
    SCOPE = Local
    DOMAIN = counter
    CNT_ATTR = ogc_fid
    -> $(Schema).queryextent (writer POSTGIS_1)

Bookmark: Outputs
Note: When running the work space with prompt you need to enter the database details. The writers contain the schema parameter as the table qualifier meaning they will all write to the same place. / They are currently set up to write new tables so the schema will need to be empty. The writers also will not create indexes om the data, You will have to do that manually.
$(Schema).cartographictext (writer POSTGIS_1)
    attributes: ogc_fid serial,PRIKEY, toid varchar(22), featurecode int2, version int2, versiondate varchar(10), theme varchar(64), changedate text, reasonforchange text, descriptivegroup varchar(254), descriptiveterm varchar(254), make varchar(12), physicallevel int2, physicalpresence varchar(16), orientation int2, referencetofeature varchar(20), anchorposition float8, font int2, height float4, textstring varchar(254), lastchangedate varchar(254), tilename varchar(50), uuid char(200), loaddate date, style_description varchar(254), style_code varchar(20), colour_code varchar(1), font_code varchar(1), rotation int2, geo_x float8, geo_y float8,
      anchor varchar(254), fontname varchar(254), fontcolour_hex varchar(10), fontcolour_rgb varchar(20)
$(Schema).topographicline (writer POSTGIS_1)
    attributes: ogc_fid serial,PRIKEY, toid varchar(22), featurecode int2, version int2, versiondate varchar(10), theme varchar(64), changedate text, reasonforchange text, descriptivegroup varchar(254), descriptiveterm varchar(254), make varchar(12), physicallevel int2, physicalpresence varchar(16), referencetofeature varchar(20), lastchangedate varchar(254), tilename varchar(50), uuid char(200), loaddate date, style_description varchar(254), style_code varchar(20)
$(Schema).topographicarea (writer POSTGIS_1)
    attributes: ogc_fid serial,PRIKEY, toid varchar(22), featurecode int2, version int2, versiondate varchar(10), theme varchar(64), changedate text, reasonforchange text, descriptivegroup varchar(254), descriptiveterm varchar(254), make varchar(12), physicallevel int2, physicalpresence varchar(16), referencetofeature varchar(20), lastchangedate varchar(254), tilename varchar(50), uuid char(200), loaddate date, style_description varchar(254), style_code varchar(20)
$(Schema).cartographicsymbol (writer POSTGIS_1)
    attributes: ogc_fid serial,PRIKEY, toid varchar(22), featurecode int2, version int2, versiondate varchar(10), theme varchar(64), changedate text, reasonforchange text, descriptivegroup varchar(254), descriptiveterm varchar(254), make varchar(12), physicallevel int2, physicalpresence varchar(16), orientation int2, referencetofeature varchar(20), lastchangedate varchar(254), tilename varchar(50), uuid char(200), loaddate date, style_description varchar(254), style_code varchar(20)
$(Schema).boundaryline (writer POSTGIS_1)
    attributes: ogc_fid serial,PRIKEY, toid varchar(22), featurecode int2, version int2, versiondate varchar(10), theme varchar(64), changedate text, reasonforchange text, descriptivegroup varchar(254), descriptiveterm varchar(254), make varchar(12), physicallevel int2, physicalpresence varchar(16), referencetofeature varchar(20), lastchangedate varchar(254), tilename varchar(50), uuid char(200), loaddate date, style_description varchar(254), style_code varchar(20)
$(Schema).topographicpoint (writer POSTGIS_1)
    attributes: ogc_fid serial,PRIKEY, toid varchar(22), featurecode int2, version int2, versiondate varchar(10), theme varchar(64), changedate text, reasonforchange text, descriptivegroup varchar(254), descriptiveterm varchar(254), make varchar(12), physicallevel int2, physicalpresence varchar(16), referencetofeature varchar(20), lastchangedate varchar(254), tilename varchar(50), uuid char(200), loaddate date, style_description varchar(254), style_code varchar(20)
$(Schema).queryextent (writer POSTGIS_1)
    attributes: ogc_fid serial,PRIKEY, tilename varchar(10),BTREE, loaddate timestamp, filename varchar(50)

Bookmark: Area Extent
Note: Creates Load date
TimeStamper
    FMT = XML DateTime (^Y-^m-^dT^H:^M:^S)
    TIME_ATTR = loaddate
    -> AttributeSplitter_3
Note: Splits the base name
AttributeSplitter_3
    TRIM_OPTION = Both
    DELIMITER = -
    DROP_EMPTY_PARTS = No
    ATTR_NAME = fme_basename
    LIST_NAME = _lstTileName
    -> AttributeCreator_3
AttributeCreator_3
    ATTR_LIST = tilename,@Value(_lstTileName{1})
    -> AttributeCopier
Note: Copies fme_basename attribute into filename
AttributeCopier
    ATTR_LIST = filename,fme_basename
    -> Counter_7
